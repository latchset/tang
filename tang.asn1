Tang DEFINITIONS EXPLICIT TAGS ::= BEGIN

TangMessage ::= CHOICE {
  error   [0] TangMessageError,
  rec-req [1] TangMessageRecoverRequest,
  rec-rep [2] TangMessageRecoverReply,
  adv-req [3] TangMessageAdvertiseRequest,
  adv-rep [4] TangMessageAdvertiseReply,
  ...
}

TangMessageError ::= ENUMERATED {
  internal            (1),
  invalid-request     (2),
  notfound-key        (3),
  ...
}

TangMessageRecoverRequest ::= SEQUENCE {
  key    [0] TangKey,
  x      [1] OCTET STRING,
  ...
}

TangMessageRecoverReply ::= SEQUENCE {
  y      [0] OCTET STRING,
  ...
}

TangMessageAdvertiseRequest ::= SEQUENCE {
  keys   [0] SET OF TangKey,
  ...
}

TangMessageAdvertiseReply ::= SEQUENCE {
  body   [0] TangMessageAdvertiseReplyBody,
  sigs   [1] SET (SIZE(1..MAX)) OF TangSignature,
  ...
}

TangMessageAdvertiseReplyBody ::= SEQUENCE {
  sigs   [0] SET (SIZE(1..MAX)) OF TangKey,
  recs   [1] SET (SIZE(1..MAX)) OF TangKey,
  ...
}

TangSignature ::= SEQUENCE {
  type   [0] OBJECT IDENTIFIER,
  sig    [1] OCTET STRING, -- ECDSA-Sig-Value
  ...
}

TangKey ::= SEQUENCE {
  grp  [0] OBJECT IDENTIFIER,
  key  [1] OCTET STRING,
  ...
}

END
